// Copyright (c) 2009-2011, Benjamin Drung <benjamin.drung@gmail.com>
//
// copypaste_config.ulp - configuration file for copy/paste ULP
//
// Permission to use, copy, modify, and/or distribute this software for any
// purpose with or without fee is hereby granted, provided that the above
// copyright notice and this permission notice appear in all copies.
//
// THE SOFTWARE IS PROVIDED "AS IS" AND THE AUTHOR DISCLAIMS ALL WARRANTIES
// WITH REGARD TO THIS SOFTWARE INCLUDING ALL IMPLIED WARRANTIES OF
// MERCHANTABILITY AND FITNESS. IN NO EVENT SHALL THE AUTHOR BE LIABLE FOR
// ANY SPECIAL, DIRECT, INDIRECT, OR CONSEQUENTIAL DAMAGES OR ANY DAMAGES
// WHATSOEVER RESULTING FROM LOSS OF USE, DATA OR PROFITS, WHETHER IN AN
// ACTION OF CONTRACT, NEGLIGENCE OR OTHER TORTIOUS ACTION, ARISING OUT OF
// OR IN CONNECTION WITH THE USE OR PERFORMANCE OF THIS SOFTWARE.

#require 5.10

// constants
int FALSE = 0;
int TRUE = !FALSE;

string common_signal[];
int n_common_signal = 0;

// layer number of air wires
int layer_unrouted = 19;

// common signal for all modules
common_signal[n_common_signal++] = "VSS";
common_signal[n_common_signal++] = "VDD";
common_signal[n_common_signal++] = "GND";
common_signal[n_common_signal++] = "VCC";
common_signal[n_common_signal++] = "V+";
common_signal[n_common_signal++] = "V-";

// file names
string basedir = path_scr[0];
string board_filename = basedir + "/clipboard_board.scr";
string copypaste_info = "copypaste-info.txt";
string paste_script = basedir + "/paste.scr";
string schematic_filename = basedir + "/clipboard_schematic.scr";

// Temporary net prefix required for renaming nets which are automatically
// generated by Eagle when placing parts
string temporary_net_prefix = "COPYPASTE_";

// append new schematic sheet(s)
int append_sheets = TRUE;

// copy either relative to lower left corner or to origin
int copy_relative_to_lower_left_corner = FALSE;

// debug modus (prints informations into copypaste info file)
int debug = FALSE;

// include list of renamed elements in copypaste info file
int include_rename_list = FALSE;

// run electric rule check before finishing paste script
int run_erc = FALSE;

// run ratsnest before finishing paste script
int run_ratsnest = TRUE;

// The warning message about a part not having a user definable value is
// disabled while the paste script is running. Specify whether this warning
// message should be enabled after running the paste script or not.
int enable_PartHasNoUserDefinableValue_warning = TRUE;
